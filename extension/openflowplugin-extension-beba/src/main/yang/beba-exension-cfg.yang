module beba-extension {
    yang-version 1;
    namespace "urn:opendaylight:params:xml:ns:yang:controller:config:openflowplugin:beba:config";
    prefix "bebaExt-cfg";

    import config {prefix config; revision-date 2013-04-05; }

    description
        "openflow extension for beba - config";

    revision "2017-03-07" {
        description
            "Initial revision";
    }

    identity beba-extension-provider {
        base config:service-type;
        config:java-class "org.opendaylight.openflowplugin.extension.vendor.beba.BebaExtensionProvider";
    }
}
