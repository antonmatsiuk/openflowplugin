module beba-instruction {
    yang-version 1;

    namespace "urn:opendaylight:openflowjava:beba:instruction";
    prefix "beba-instr";

    import openflow-types {prefix oft;}
    import yang-ext {prefix ext; revision-date "2013-07-09";}
    import openflow-protocol {prefix ofproto; revision-date "2013-07-31";}
    import openflow-instruction {prefix ofinstruction;}
    import openflow-action {prefix ofaction;}
    import openflow-augments {prefix ofaugments; revision-date "2015-02-25";}

    description
        "Beba openflow experimental instructions.";

    revision "2017-03-07" {
        description "Initial revision";
    }

    identity port-mod-instr {
        description "Port modification experimenter instruction";
        base oft:instruction-base;
    }

    identity in-switch-packet-gen-instr {
        description "InSP packet generation experimenter instruction";
        base oft:instruction-base;
    }

    grouping port-mod-grouping {
        container port-mod {
            leaf port-id {
                type uint32;
            }
            leaf conf {
                type uint32;
            }
            leaf mask {
                type uint32;
            }
        }
    }

    grouping in-switch-packet-gen-grouping {
        container in-switch-packet-gen {
            leaf pkttmp-id {
                type uint32;
            }
            uses ofaction:actions-grouping;
//            leaf-list actions {
//                type oft:action-type;
//               type identityref {
//                   base oft:action-base;
//                   }
//            }
        }
    }

    grouping beba-instruction-grouping {
        choice beba-instruction-choice {
            case port-mod-case {
                uses port-mod-grouping;
            }
            case in-switch-packet-gen-case {
                uses in-switch-packet-gen-grouping;
            }
        }
    }

    augment "/ofinstruction:instruction-container/ofinstruction:instruction-choice/ofaugments:experimenter-id-case/ofaugments:experimenter"{
      ext:augment-identifier "beba-experimenter-instr";
      leaf beba-instr-type {
          type uint32;
      }
      uses beba-instruction-grouping;
    }
}
