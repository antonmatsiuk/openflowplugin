module beba-message {
    yang-version 1;

    namespace "urn:opendaylight:openflowjava:beba";
    prefix "beba-msg";

    import openflow-types {prefix oft;}
    import yang-ext {prefix ext; revision-date "2013-07-09";}
    import openflow-protocol {prefix ofproto; revision-date "2013-07-31";}
    import openflow-instruction {prefix ofinstruction;}

    description
        "Beba openflow message extensions.";

    revision "2017-03-07" {
        description "Initial revision";
    }

        typedef state-mod-command {
            type enumeration {
                enum OFPSC_EXP_STATEFUL_TABLE_CONFIG {
                    value 0;
                }
                enum OFPSC_EXP_SET_L_EXTRACTOR {
                    value 1;
                }
                enum OFPSC_EXP_SET_U_EXTRACTOR {
                    value 2;
                }
                enum OFPSC_EXP_SET_FLOW_STATE {
                    value 3;
                }
                enum OFPSC_EXP_DEL_FLOW_STATE {
                    value 4;
                }
                enum OFPSC_EXP_SET_GLOBAL_STATE {
                    value 5;
                }
                enum OFPSC_EXP_RESET_GLOBAL_STATE {
                    value 6;
                }
            }
        }

        typedef event-mod-command {
            type enumeration {
                enum OFPSC_ADD_EVENT {
                    value 0;
                }
                enum OFPSC_DEL_EVENT {
                    value 1;
                }
            }
        }

        typedef event-type {
            type enumeration {
                enum OFPE_PORT_STATE {
                    value 0;
                }
                enum OFPE_FLOW_EXPIRED {
                    value 1;
                }
                enum OFPE_TIMER_EXPIRED {
                    value 2;
                }
                enum OFPE_BUCKET_STATE {
                    value 3;
                }
            }
        }

        typedef event-react-type {
            type enumeration {
                enum OFPR_EXP_INSTRUCTION {
                    value 0;
                }
            }
        }

        typedef pkttmp-mod-command {
            type enumeration {
                enum OFPSC_ADD_PKTTMP {
                    value 0;
                }
                enum OFPSC_DEL_PKTTMP {
                    value 1;
                }
            }
        }

        //STATE_MOD
        grouping statemod-cmd-grouping {
            choice cmd-choice {
                case stateful-table-config-case {
                    container stateful-table-config {
                        leaf table-id {
                            type uint8;
                        }
                        leaf stateful {
                            type uint8;
                        }
                    }
                }
                case set-extractor-case {
                    container set-extractor{
                        leaf table-id {
                            type uint8;
                        }
                        leaf field-count {
                            type uint32;
                        }
                        leaf-list fields {
                            type uint32;
                            max-elements 6;
                        }
                    }
                }
                case set-flow-state-case {
                    container set-flow-state {
                        leaf table-id {
                            type uint8;
                        }
                        leaf key-len {
                            type uint32;
                        }
                        leaf state {
                            type uint32;
                        }
                        leaf state-mask {
                            type uint32;
                        }
                        leaf hard-rollback {
                            type uint32;
                        }
                        leaf idle-rollback {
                            type uint32;
                        }
                        leaf hard-timeout {
                            type uint32;
                        }
                        leaf idle-timeout {
                            type uint32;
                        }
                        leaf-list keys {
                            type uint8;
                            max-elements 48;
                        }
                    }
                }
                case del-flow-state-case {
                    container del-flow-state {
                        leaf table-id {
                            type uint8;
                        }
                        leaf key-len {
                            type uint32;
                        }
                        leaf-list keys {
                            type uint8;
                            max-elements 48;
                        }
                    }
                }
                case set-global-state-case {
                    container set-global-state {
                        leaf global-state {
                            type uint32;
                        }
                        leaf global-state-mask{
                            type uint32;
                        }
                    }
                }
            }
        }

        //PKTTMP_MOD
        grouping pkttmp-cmd-grouping {
            choice cmd-choice {
                case add-pkttmp-case {
                    container add-pkttmp{
                        leaf data{
                            type binary;
                        }
                    }
                }
                case del-pkttmp-case{
                }
            }
        }

        //EVENT_MOD
        grouping port-state-react-grouping{
            choice react-choice{
                case exp-instr-case{
                    container exp-instr{
                        uses ofinstruction:instructions-grouping;
                    }
                }
            }
        }

        grouping add-event-grouping {
            choice ev-choice {
                case port-state-case{
                    container port-state{
                        leaf port-no{
                            type uint32;
                        }
                        leaf state{
                            type uint32;
                        }
                        leaf react-type{
                            type uint16;
                        }
                        uses port-state-react-grouping;
                    }
                }
                case flow-expired-case{
                    //TODO
                }
                case timer-expired-case{
                    //TODO
                }
                case bucket-state-case{
                    //TODO
                }
            }
        }

        grouping eventmod-cmd-grouping {
            choice cmd-choice {
                case add-event-mod-case {
                    container add-event-mod {
                        leaf event-id {
                            type uint32;
                        }
                        leaf ev-type {
                            type event-type;
                        }
                        uses add-event-grouping;
                    }
                }
                case del-event-mod-case {
                    container del-event-mod {
                        leaf event-id {
                            type uint32;
                        }
                    }
                }
            }
        }

        grouping msg-pkttmp-mod-grouping {
            container msg-pkttmp-mod{
                leaf command {
                    type pkttmp-mod-command;
                }
                leaf pkttmpid {
                    type uint32;
                }
                uses pkttmp-cmd-grouping;
            }
        }

        grouping msg-event-mod-grouping {
            container msg-pkttmp-mod{
                leaf command {
                    type event-mod-command;
                }
                leaf eventid {
                    type uint32;
                }
                uses eventmod-cmd-grouping;
            }
        }

        grouping msg-state-mod-grouping {
            container msg-state-mod {
                leaf command {
                    type state-mod-command;
                }
                uses statemod-cmd-grouping;
            }
        }

        grouping msg-state-changed-grouping {
            container msg-state-changed {
                leaf table-id {
                    type uint8;
                }
                leaf old-state {
                    type uint32;
                }
                leaf new-state {
                    type uint32;
                }
                leaf state-mask {
                    type uint32;
                }
                leaf key-len {
                    type uint32;
                }
                leaf-list keys {
                    type uint8;
                    max-elements 48;
                }
            }
        }

        grouping msg-flow-notif-grouping {
            container msg-flow-notif {
                leaf ntf-type {
                    type uint32;
                }
                leaf table-id {
                    type uint32;
                }
                leaf ofl-match-header {
                    type identityref {
                        base oft:match-type-base;
                    }
                }
                leaf instruction-num {
                    type uint32;
                }
                leaf-list instructions {
                    type identityref {
                        base oft:instruction-base;
                    }
                }
            }
        }

        //ofp-exp-beba-message
        augment "/ofproto:experimenter/ofproto:input/ofproto:experimenter-data-of-choice" {
            ext:augment-identifier "ofj-aug-beba-msg";
            case msg-pkttmp-mod-case {
                uses msg-pkttmp-mod-grouping;
            }
            case msg-event-mod-case {
                uses msg-event-mod-grouping;
            }
            case msg-state-mod-case{
                uses msg-state-mod-grouping;
            }
            case msg-state-changed-case {
                uses msg-state-changed-grouping;
            }
            case msg-flow-notif-case {
                uses msg-flow-notif-grouping;
            }
        }
}
